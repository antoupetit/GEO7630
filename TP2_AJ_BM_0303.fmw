FME workspace TP2_AJ_BM_0303.fmw

Parameters:
- SourceDataset_SHAPEFILE = https://donnees.montreal.ca/dataset/5ea29f40-1b5b-4f34-85b3-7c67088ff536/resource/234c8ee4-d9d8-4bb1-b957-3e5cd495a5aa/download/reseau_cyclable.zip   # Source Esri Shapefile(s)
- SourceDataset_CSV2_3 = https://donnees.montreal.ca/dataset/667342f7-f667-4c3c-9837-65e81312cd8d/resource/a2bc8014-488c-495d-941b-e7ae1999d1bd/download/impacts-entraves-travaux-en-cours.csv   # Source CSV (Comma Separated Value) File(s)
- SourceDataset_CSV2 = https://donnees.montreal.ca/dataset/667342f7-f667-4c3c-9837-65e81312cd8d/resource/cc41b532-f12d-40fb-9f55-eb58c9a2b12b/download/entraves-travaux-en-cours.csv   # Source CSV (Comma Separated Value) File(s)
- SourceDataset_SHAPEFILE_9 = https://donnees.montreal.ca/dataset/dbdfbdba-0725-470d-a23e-da69dbedc4e6/resource/ed333be1-bce6-4890-b0de-9788d5ca0774/download/ilots-de-chaleur-images-satellite-2023.zip   # Source Esri Shapefile(s)
- SourceDataset_SHAPEFILE_7 = https://donnees.montreal.ca/dataset/2e9e4d2f-173a-4c3d-a5e3-565d79baa27d/resource/c57baaf4-0fa8-4aa4-9358-61eb7457b650/download/shapefile.zip   # Source Esri Shapefile(s)
- SourceDataset_SHAPEFILE_6 = https://donnees.montreal.ca/dataset/984f7a68-ab34-4092-9204-4bdfcca767c5/resource/70c1f8c7-91a0-4553-b602-89c3edb959b5/download/geobase.zip   # Source Esri Shapefile(s)
- SourceDataset_SHAPEFILE_8 = https://donnees.montreal.ca/dataset/cd722e22-376b-4b89-9bc2-7c7ab317ef6b/resource/5a81f6c5-e3e7-4c0e-9ccf-a4ba2cab77ba/download/collisions_routieres.zip   # Source Esri Shapefile(s)
- DestDataset_POSTGIS = FH791176   # Connection
- SourceDataset_POSTGIS_6 = FH791176   # Connection
- SourceDataset_POSTGIS_5 = FH791176   # Connection
- SourceDataset_POSTGIS = FH791176   # Connection
- SourceDataset_GEOTIFF = C:\temp\mnt_mtl.tif   # Source GeoTIFF File(s) or URL(s)
- SourceDataset_POSTGIS_RASTER_3 = FH791176   # Connection

Readers:
- SHAPEFILE_1: SHAPEFILE from $(SourceDataset_SHAPEFILE)
- CSV2_1: CSV2 from $(SourceDataset_CSV2)
- CSV2_2: CSV2 from $(SourceDataset_CSV2_3)
- SHAPEFILE_2: SHAPEFILE from $(SourceDataset_SHAPEFILE_9)
- SHAPEFILE_3: SHAPEFILE from $(SourceDataset_SHAPEFILE_7)
- SHAPEFILE_4: SHAPEFILE from $(SourceDataset_SHAPEFILE_6)
- SHAPEFILE_5: SHAPEFILE from $(SourceDataset_SHAPEFILE_8)
- GEOTIFF_1: GEOTIFF from $(SourceDataset_GEOTIFF)
- POSTGIS_2: POSTGIS from $(SourceDataset_POSTGIS)
- POSTGIS_3: POSTGIS from $(SourceDataset_POSTGIS_6)
- POSTGIS_4: POSTGIS from $(SourceDataset_POSTGIS_5)
- POSTGIS_RASTER_2: POSTGIS_RASTER from $(SourceDataset_POSTGIS_RASTER_3)

Writers:
- POSTGIS_1: POSTGIS to $(DestDataset_POSTGIS)

Note: fichier du Réseau_routier de montreal. Le champ Tvoie permet d'identifier les voies principales pour obtenir un buffer autour et donner une valeur d'indice aux troncons de piste cyclables

Bookmark: Réseau_cyclable
reseau_cyclable (reader SHAPEFILE_1)
    attributes: ID_CYCL number(18,0), ID_TRC number(18,0), AFFICHEUR_ varchar(80), AVANCEMENT varchar(80), AVANCEME_1 varchar(80), COMPTEUR_C varchar(80), LONGUEUR number(18,0), NBR_VOIE number(18,0), NOM_ARR_VI varchar(80), NOM_ARR__1 varchar(80), PROTEGE_4S varchar(80), REV_AVANCE varchar(80), REV_AVAN_1 varchar(80), ROUTE_VERT varchar(80), SAISONS4 varchar(80), SAS_VELO varchar(80), SEPARATEUR varchar(80), SEPARATE_1 varchar(80), TYPE_VOIE_ varchar(80), TYPE_VOI_1 varchar(80), TYPE_VOIE2 varchar(80), TYPE_VOI_2 varchar(116), VILLE_MTL varchar(80)
    -> Reprojector
Reprojector
    DEST = EPSG:3857
    INTERPOLATION_TYPE_NAME = Nearest Neighbor
    RASTER_CELL_SIZE = Preserve Cells
    RASTER_TOLERANCE = 0.0
    REPROJECTED -> IterativeSnipper
Note: Permet de maximiser la longueur des segments de piste cyclable / à 75m maximum.
IterativeSnipper
    DOMAIN = id_segment
    SNIPMODE = ToLength
    SnipLength = 75
    -> BulkAttributeRenamer
    <Rejected> -> Logger_3
Note: On renomme les attributs en minuscule selon la convention
BulkAttributeRenamer
    ATTRCHOICE = All Attributes
    CASE_CHANGE_TYPE = lower
    MODE_CHOICE = RENAME
    PATTERN_ACTION_DISP = CASECHANGE
    -> GeometryExtractor_2
GeometryExtractor_2
    ATTR = _geometry
    KIND_LONG = FME Binary
    REMOVE_GEOMETRY = No
    -> AttributeManager_2
    <REJECTED> -> Logger_10
Note: On rajoute des valeurs d'indice int de qualité d'usage en fonction des champs pertinents. On rajoute un champ qui compte le nombre de coordonnees pour extraire la coordonnée de fin de segment.
AttributeManager_2
    ATTR_TABLE:
      REMOVE afficheur_ (varchar(80))
      REMOVE avancement (varchar(80))
      REMOVE avanceme_1 (varchar(80))
      REMOVE compteur_c (varchar(80))
      REMOVE longueur (number(18,0))
      REMOVE nbr_voie (number(18,0))
      REMOVE nom_arr_vi (varchar(80))
      REMOVE nom_arr__1 (varchar(80))
      REMOVE rev_avance (varchar(80))
      REMOVE sas_velo (varchar(80))
      REMOVE type_voie2 (varchar(80))
      REMOVE type_voi_2 (varchar(116))
      REMOVE ville_mtl (varchar(80))
      REMOVE x_debut (real64)
      REMOVE y_debut (real64)
      REMOVE x_fin (real64)
      REMOVE y_fin (varchar(200))
      SET_TO ind_sep_voie (int64) = FME_CONDITIONAL:DEFAULT_VALUE'4'BOOL_OP;OR;COMPOSITE_TEST;1 OR 2;TEST @Value(type_voie_) = 0;TEST @Value(type_voie_) = 1'0'BOOL_OP;OR;COMPOSITE_TEST;1 OR 2;TEST @Value(type_voie_) = 2;TEST @Value(type_voie_) = 9'1'BOOL_OP;OR;COMPOSITE_TEST;1;TEST @Value(type_voie_) = 7'2'BOOL_OP;OR;COMPOSITE_TEST;1 OR 2 OR 3;TEST @Value(type_voie_) = 3;TEST @Value(type_voie_) = 6;TEST @Value(type_voie_) = 8'3'FME_NUM_CONDITIONS5___
      SET_TO n_coord (int64) = @Evaluate(@NumCoords())
      SET_TO longueur_2 (real64) = @Evaluate(@Length())
    USER_EXPOSED_ATTRIBUTES = ind_typ_voie,ind_sep_voie,ind_4_sais,ind_rev,x_debut,y_debut,x_fin,y_fin,n_coord,longueur_2
    -> FeatureJoiner_3 [RIGHT]
    -> CoordinateExtractor
Note: On extrait les coordonnées de début de chaque segment
CoordinateExtractor
    IND = 0
    MODE = Specify Coordinate
    X_ATTR = x_debut
    Y_ATTR = y_debut
    -> CoordinateExtractor_2
    <REJECTED> -> Logger_4
Note: On extrait les coordonnées de fin de chaque segment à partir du nombre de coordonnées - 1 qui nous donne la position d'index de la dernière coordonnée de chaque segment.
CoordinateExtractor_2
    IND = (@Value(n_coord)-1)
    MODE = Specify Coordinate
    X_ATTR = x_fin
    Y_ATTR = y_fin
    -> VertexCreatordebut
    -> VertexCreatorfin
    <REJECTED> -> Logger_5
Logger_5
    LOG_FEATURE = LOG_ONLY
    MAXCOORDS = 20
    MAXFEATS = 20
    MESSAGE = Feature is:
    SEVERITY = INFO
Logger_4
    LOG_FEATURE = LOG_ONLY
    MAXCOORDS = 20
    MAXFEATS = 20
    MESSAGE = Feature is:
    SEVERITY = INFO
Logger_10
    LOG_FEATURE = LOG_ONLY
    MAXCOORDS = 20
    MAXFEATS = 20
    MESSAGE = Feature is:
    SEVERITY = INFO
Logger_3
    LOG_FEATURE = LOG_ONLY
    MAXCOORDS = 20
    MAXFEATS = 20
    MESSAGE = Feature is:
    SEVERITY = INFO

Bookmark: Fichier de points de début et fin de chaque segment de piste cyclable
Note: Création d'un fichier de points de debut et fin de chaque segment de piste cyclable
VertexCreatordebut
    MEASURE_TYPE = Continuous
    MODE_NAME = Replace with Point
    XVAL = @Value(x_debut)
    YVAL = @Value(y_fin)
    -> PORV_debut [POINT]
    <REJECTED> -> Logger_6
Logger_6
    LOG_FEATURE = LOG_ONLY
    MAXCOORDS = 20
    MAXFEATS = 20
    MESSAGE = Feature is:
    SEVERITY = INFO
VertexCreatorfin
    MEASURE_TYPE = Continuous
    MODE_NAME = Replace with Point
    XVAL = @Value(x_fin)
    YVAL = @Value(y_fin)
    -> PORV_fin [POINT]
    <REJECTED> -> Logger_7
Logger_7
    LOG_FEATURE = LOG_ONLY
    MAXCOORDS = 20
    MAXFEATS = 20
    MESSAGE = Feature is:
    SEVERITY = INFO

Bookmark: Réseau_routier
geobase_mtl (reader SHAPEFILE_4)
    attributes: ID_TRC long, DEB_GCH long, FIN_GCH long, ARR_GCH varchar(200), SENS_CIR long, CLASSE long, LIE_VOIE varchar(10), TYP_VOIE varchar(15), DIR_VOIE varchar(5), NOM_VOIE varchar(50), DEB_DRT long, FIN_DRT long, ARR_DRT varchar(200), LIM_GCH varchar(30), LIM_DRT varchar(30), POSITION long
    -> Reprojector_5
Reprojector_5
    DEST = EPSG:3857
    INTERPOLATION_TYPE_NAME = Nearest Neighbor
    RASTER_CELL_SIZE = Preserve Cells
    RASTER_TOLERANCE = 0.0
    REPROJECTED -> BulkAttributeRenamer_5
Note: On renomme les attributs en minuscule selon la convention
BulkAttributeRenamer_5
    ATTRCHOICE = All Attributes
    CASE_CHANGE_TYPE = lower
    MODE_CHOICE = RENAME
    PATTERN_ACTION_DISP = CASECHANGE
    -> AttributeFilter
    -> FeatureJoiner_4 [RIGHT]
Note: Filtre pour ne garder que les voies principales
AttributeFilter
    ATTR_NAME = typ_voie
    ATTR_VALUES = <Empty>,<Missing>,<Null>,<Unfiltered>,autoroute
    autoroute -> Bufferer_4
    autoroute -> Bufferer_3
    autoroute -> Bufferer_2
Note: Serie de buffer autour des voies principales
Bufferer_2
    ANGLE = 22.5
    CAP_STYLE = Arc
    CORNER_STYLE = Arc
    MODE = AREA
    OFFSET = 50
    OFFSET_UNITS = NONE
    PRECISION = APPROX
    BUFFERED -> Clipper_4 [CLIPPER]
    BUFFERED -> AreaOnAreaOverlayer_4 [AREA]
    <REJECTED> -> Logger_22
Note: S'assure de ne pas avoir 2 objets de polygones qui se superposent afin de ne pas surestimer l'indice de proximité des voies principaes
AreaOnAreaOverlayer_4
    ACCUM_ATTRS_NAME = Merge Incoming Attributes
    CLEANING_TOLERANCE = Automatic
    CONNECT_Z_MODE = First Wins
    DEAGGREGATE_INPUT = Yes
    OVC_ATTR = _overlaps
    AREA -> AttributeManager_11
    <REJECTED> -> Logger_27
Logger_27
    LOG_FEATURE = LOG_ONLY
    MAXCOORDS = 20
    MAXFEATS = 20
    MESSAGE = Feature is:
    SEVERITY = INFO
Note: Ajout de svaleurs d'indice de proximité des voies principales
AttributeManager_11
    ATTR_TABLE = SET_TO ind_voie_princ (int64) = -3
    USER_EXPOSED_ATTRIBUTES = ind_voie_princ
    -> Junction_2
Logger_22
    LOG_FEATURE = LOG_ONLY
    MAXCOORDS = 20
    MAXFEATS = 20
    MESSAGE = Feature is:
    SEVERITY = INFO
Bufferer_3
    ANGLE = 22.5
    CAP_STYLE = Arc
    CORNER_STYLE = Arc
    MODE = AREA
    OFFSET = 200
    OFFSET_UNITS = NONE
    PRECISION = APPROX
    BUFFERED -> Clipper_3 [CLIPPER]
    BUFFERED -> Clipper_4 [CANDIDATE]
    <REJECTED> -> Logger_23
Note: Enlever zones où buffer s'entrecoupent
Clipper_4
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AreaOnAreaOverlayer_5 [AREA]
    <REJECTED> -> Logger_25
AreaOnAreaOverlayer_5
    ACCUM_ATTRS_NAME = Merge Incoming Attributes
    CLEANING_TOLERANCE = Automatic
    CONNECT_Z_MODE = First Wins
    DEAGGREGATE_INPUT = Yes
    OVC_ATTR = _overlaps
    AREA -> AttributeManager_10
    <REJECTED> -> Logger_28
AttributeManager_10
    ATTR_TABLE = SET_TO ind_voie_princ (int64) = -2
    USER_EXPOSED_ATTRIBUTES = ind_voie_princ
    -> Junction_2
Logger_28
    LOG_FEATURE = LOG_ONLY
    MAXCOORDS = 20
    MAXFEATS = 20
    MESSAGE = Feature is:
    SEVERITY = INFO
Logger_25
    LOG_FEATURE = LOG_ONLY
    MAXCOORDS = 20
    MAXFEATS = 20
    MESSAGE = Feature is:
    SEVERITY = INFO
Logger_23
    LOG_FEATURE = LOG_ONLY
    MAXCOORDS = 20
    MAXFEATS = 20
    MESSAGE = Feature is:
    SEVERITY = INFO
Bufferer_4
    ANGLE = 22.5
    CAP_STYLE = Arc
    CORNER_STYLE = Arc
    MODE = AREA
    OFFSET = 500
    OFFSET_UNITS = NONE
    PRECISION = APPROX
    BUFFERED -> Clipper_3 [CANDIDATE]
    <REJECTED> -> Logger_24
Clipper_3
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AreaOnAreaOverlayer_6 [AREA]
    <REJECTED> -> Logger_26
AreaOnAreaOverlayer_6
    ACCUM_ATTRS_NAME = Merge Incoming Attributes
    CLEANING_TOLERANCE = Automatic
    CONNECT_Z_MODE = First Wins
    DEAGGREGATE_INPUT = Yes
    OVC_ATTR = _overlaps
    AREA -> AttributeManager_9
    <REJECTED> -> Logger_29
AttributeManager_9
    ATTR_TABLE = SET_TO ind_voie_princ (int64) = -1
    USER_EXPOSED_ATTRIBUTES = ind_voie_princ
    -> Junction_2
Note: Mise en union des différents niveaux d'indice de proximité des voies principales
Junction_2
    -> AttributeManager_13
Note: Ménage avant de rajouter l'indice aux voies cyclables
AttributeManager_13
    ATTR_TABLE:
      REMOVE deb_gch (int32)
      REMOVE fin_gch (int32)
      REMOVE arr_gch (varchar(200))
      REMOVE sens_cir (int32)
      REMOVE classe (int32)
      REMOVE lie_voie (varchar(10))
      REMOVE typ_voie (varchar(15))
      REMOVE dir_voie (varchar(5))
      REMOVE nom_voie (varchar(50))
      REMOVE deb_drt (int32)
      REMOVE fin_drt (int32)
      REMOVE arr_drt (varchar(200))
      REMOVE lim_gch (varchar(30))
      REMOVE lim_drt (varchar(30))
      REMOVE position (int32)
      REMOVE _clipped (char(9))
    -> SpatialFilter_3 [Filter]
Logger_29
    LOG_FEATURE = LOG_ONLY
    MAXCOORDS = 20
    MAXFEATS = 20
    MESSAGE = Feature is:
    SEVERITY = INFO
Logger_26
    LOG_FEATURE = LOG_ONLY
    MAXCOORDS = 20
    MAXFEATS = 20
    MESSAGE = Feature is:
    SEVERITY = INFO
Logger_24
    LOG_FEATURE = LOG_ONLY
    MAXCOORDS = 20
    MAXFEATS = 20
    MESSAGE = Feature is:
    SEVERITY = INFO
Note: Ajout des indices aux voies cyclablles
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_4
    FAILED -> AttributeManager_14
    <REJECTED> -> Logger_30
Note: Ajout de valeur d'indice pour les pistes à plus de 500m des voies principales
AttributeManager_14
    ATTR_TABLE = SET_TO ind_voie_princ (int64) = 1
    USER_EXPOSED_ATTRIBUTES = ind_voie_princ
    -> Junction_4
Note: Mise en union de tous les indice de proximité des voies principales
Junction_4
    -> SpatialFilter_4 [Candidate]
Logger_30
    LOG_FEATURE = LOG_ONLY
    MAXCOORDS = 20
    MAXFEATS = 20
    MESSAGE = Feature is:
    SEVERITY = INFO

Bookmark: Espaces_verts
Espace_Vert (reader SHAPEFILE_3)
    attributes: OBJECTID long, Type varchar(200), Lien varchar(200), Nom varchar(200), NUM_INDEX varchar(200), SUPERFICIE varchar(200), PROPRIETE varchar(200), GESTION varchar(200), COMPETENCE varchar(200), TYPO1 varchar(200), TYPO2 varchar(200)
    -> Reprojector_4
Reprojector_4
    DEST = EPSG:3857
    INTERPOLATION_TYPE_NAME = Nearest Neighbor
    RASTER_CELL_SIZE = Preserve Cells
    RASTER_TOLERANCE = 0.0
    REPROJECTED -> BulkAttributeRenamer_4
    REPROJECTED -> LineOnAreaOverlayer [AREA]
Note: On renomme les attributs en minuscule selon la convention
BulkAttributeRenamer_4
    ATTRCHOICE = All Attributes
    CASE_CHANGE_TYPE = lower
    MODE_CHOICE = RENAME
    PATTERN_ACTION_DISP = CASECHANGE
    -> Bufferer_50
    -> Bufferer_100
    -> Bufferer_200
Note: Serie de buffer autour des espaces verts
Bufferer_50
    ANGLE = 22.5
    CAP_STYLE = Arc
    CORNER_STYLE = Arc
    MODE = AREA
    OFFSET = 50
    OFFSET_UNITS = NONE
    PRECISION = APPROX
    BUFFERED -> Clipper_2 [CLIPPER]
    BUFFERED -> AreaOnAreaOverlayer [AREA]
    <REJECTED> -> Logger_13
Note: S'assure de ne pas avoir 2 objets de polygones qui se superposent afin de ne pas surestimer l'indice d'espace vert
AreaOnAreaOverlayer
    ACCUM_ATTRS_NAME = Merge Incoming Attributes
    CLEANING_TOLERANCE = Automatic
    CONNECT_Z_MODE = First Wins
    DEAGGREGATE_INPUT = Yes
    OVC_ATTR = _overlaps
    AREA -> AttributeManager_5
    <REJECTED> -> Logger_18
Note: Attribution de valeur d'indice de proximité aux espaces verts
AttributeManager_5
    ATTR_TABLE = SET_TO ind_vert (int64) = 3
    USER_EXPOSED_ATTRIBUTES = ind_vert
    -> Junction
Logger_18
    LOG_FEATURE = LOG_ONLY
    MAXCOORDS = 20
    MAXFEATS = 20
    MESSAGE = Feature is:
    SEVERITY = INFO
Logger_13
    LOG_FEATURE = LOG_ONLY
    MAXCOORDS = 20
    MAXFEATS = 20
    MESSAGE = Feature is:
    SEVERITY = INFO
Bufferer_100
    ANGLE = 22.5
    CAP_STYLE = Arc
    CORNER_STYLE = Arc
    MODE = AREA
    OFFSET = 100
    OFFSET_UNITS = NONE
    PRECISION = APPROX
    BUFFERED -> Clipper [CLIPPER]
    BUFFERED -> Clipper_2 [CANDIDATE]
    <REJECTED> -> Logger_14
Note: Enlever zones où buffer s'entrecoupent
Clipper_2
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AreaOnAreaOverlayer_2 [AREA]
    <REJECTED> -> Logger_16
AreaOnAreaOverlayer_2
    ACCUM_ATTRS_NAME = Merge Incoming Attributes
    CLEANING_TOLERANCE = Automatic
    CONNECT_Z_MODE = First Wins
    DEAGGREGATE_INPUT = Yes
    OVC_ATTR = _overlaps
    AREA -> AttributeManager_6
    <REJECTED> -> Logger_19
AttributeManager_6
    ATTR_TABLE = SET_TO ind_vert (int64) = 2
    USER_EXPOSED_ATTRIBUTES = ind_vert
    -> Junction
Logger_19
    LOG_FEATURE = LOG_ONLY
    MAXCOORDS = 20
    MAXFEATS = 20
    MESSAGE = Feature is:
    SEVERITY = INFO
Logger_16
    LOG_FEATURE = LOG_ONLY
    MAXCOORDS = 20
    MAXFEATS = 20
    MESSAGE = Feature is:
    SEVERITY = INFO
Logger_14
    LOG_FEATURE = LOG_ONLY
    MAXCOORDS = 20
    MAXFEATS = 20
    MESSAGE = Feature is:
    SEVERITY = INFO
Bufferer_200
    ANGLE = 22.5
    CAP_STYLE = Arc
    CORNER_STYLE = Arc
    MODE = AREA
    OFFSET = 200
    OFFSET_UNITS = NONE
    PRECISION = APPROX
    BUFFERED -> Clipper [CANDIDATE]
    <REJECTED> -> Logger_15
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AreaOnAreaOverlayer_3 [AREA]
    <REJECTED> -> Logger_17
AreaOnAreaOverlayer_3
    ACCUM_ATTRS_NAME = Merge Incoming Attributes
    CLEANING_TOLERANCE = Automatic
    CONNECT_Z_MODE = First Wins
    DEAGGREGATE_INPUT = Yes
    OVC_ATTR = _overlaps
    AREA -> AttributeManager_7
    <REJECTED> -> Logger_20
AttributeManager_7
    ATTR_TABLE = SET_TO ind_vert (int64) = 1
    USER_EXPOSED_ATTRIBUTES = ind_vert
    -> Junction
Note: Mise en union des 3 buffers dindice d'espace vert
Junction
    -> AttributeManager_8
Note: Ménage avant de rajouter l'indice aux pistes cyclables
AttributeManager_8
    ATTR_TABLE:
      REMOVE type (varchar(200))
      REMOVE lien (varchar(200))
      REMOVE nom (varchar(200))
      REMOVE num_index (varchar(200))
      REMOVE superficie (varchar(200))
      REMOVE propriete (varchar(200))
      REMOVE gestion (varchar(200))
      REMOVE competence (varchar(200))
      REMOVE typo1 (varchar(200))
      REMOVE typo2 (varchar(200))
      REMOVE _overlaps (uint32)
      REMOVE _clipped (char(9))
    -> SpatialFilter_2 [Filter]
Logger_20
    LOG_FEATURE = LOG_ONLY
    MAXCOORDS = 20
    MAXFEATS = 20
    MESSAGE = Feature is:
    SEVERITY = INFO
Logger_17
    LOG_FEATURE = LOG_ONLY
    MAXCOORDS = 20
    MAXFEATS = 20
    MESSAGE = Feature is:
    SEVERITY = INFO
Logger_15
    LOG_FEATURE = LOG_ONLY
    MAXCOORDS = 20
    MAXFEATS = 20
    MESSAGE = Feature is:
    SEVERITY = INFO
Note: Associer l'indice de proximité aux espaces verts avec les troncons de piste cyclables et autres indices déjà calculés
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_3
    FAILED -> AttributeManager_12
    <REJECTED> -> Logger_21
AttributeManager_12
    ATTR_TABLE = SET_TO ind_vert (int64) = 0
    USER_EXPOSED_ATTRIBUTES = ind_vert
    -> Junction_3
Note: Mettre en union les troncons avec des indices nuls et non-nuls de proximité aux espaces verts
Junction_3
    -> SpatialFilter_3 [Candidate]
Logger_21
    LOG_FEATURE = LOG_ONLY
    MAXCOORDS = 20
    MAXFEATS = 20
    MESSAGE = Feature is:
    SEVERITY = INFO

Bookmark: Collisions_routières - indice de danger des pistes cyclables
collisions_routieres (reader SHAPEFILE_5)
    attributes: NO_SEQ_COL varchar(254), JR_SEMN_AC varchar(254), DT_ACCDN date, CD_MUNCP long, NO_CIVIQ_A long, SFX_NO_CIV varchar(254), BORNE_KM_A double, RUE_ACCDN varchar(254), TP_REPRR_A long, ACCDN_PRES varchar(254), NB_METRE_D long, CD_GENRE_A long, CD_SIT_PRT long, CD_ETAT_SU long, CD_ECLRM long, CD_ENVRN_A long, NO_ROUTE long, CD_CATEG_R long, CD_ETAT_CH long, CD_ASPCT_R long, CD_LOCLN_A long, CD_POSI_AC long, CD_CONFG_R long, CD_ZON_TRA long, CD_PNT_CDR varchar(254), CD_PNT_C_1 varchar(254), CD_COND_ME long, NB_VEH_IMP long, NB_MORTS long, NB_BLESSES long,
      NB_BLESS_1 long, HEURE_ACCD varchar(254), AN long, NB_VICTIME long, GRAVITE varchar(254), REG_ADM varchar(254), MRC varchar(254), nb_automob long, nb_camionL long, nb_outil_e long, nb_tous_au long, nb_bicycle long, nb_cyclomo long, nb_motocyc long, nb_taxi long, nb_urgence long, nb_motonei long, nb_VHR long, nb_autres_ long, nb_veh_non long, NB_DECES_P long, NB_BLESS_2 long, NB_VICTI_1 long, NB_DECES_M long, NB_BLESS_3 long, NB_VICTI_2 long, NB_DECES_V long, NB_BLESS_4 long, NB_VICTI_3 long, VITESSE_AU long,
      LOC_X double, LOC_Y double, LOC_COTE_Q varchar(254), LOC_COTE_P long, LOC_DETACH varchar(254), LOC_IMPREC varchar(254), LOC_LONG float, LOC_LAT float
    -> Reprojector_6
Reprojector_6
    DEST = EPSG:3857
    INTERPOLATION_TYPE_NAME = Nearest Neighbor
    RASTER_CELL_SIZE = Preserve Cells
    RASTER_TOLERANCE = 0.0
    REPROJECTED -> BulkAttributeRenamer_6
Note: On renomme les attributs en minuscule selon la convention
BulkAttributeRenamer_6
    ATTRCHOICE = All Attributes
    CASE_CHANGE_TYPE = lower
    MODE_CHOICE = RENAME
    PATTERN_ACTION_DISP = CASECHANGE
    -> AttributeManager
Note: Ménage
AttributeManager
    ATTR_TABLE:
      REMOVE jr_semn_ac (varchar(254))
      REMOVE dt_accdn (date)
      REMOVE cd_muncp (int32)
      REMOVE no_civiq_a (int32)
      REMOVE sfx_no_civ (varchar(254))
      REMOVE borne_km_a (real64)
      REMOVE rue_accdn (varchar(254))
      REMOVE tp_reprr_a (int32)
      REMOVE accdn_pres (varchar(254))
      REMOVE nb_metre_d (int32)
      REMOVE cd_genre_a (int32)
      REMOVE cd_sit_prt (int32)
      REMOVE cd_etat_su (int32)
      REMOVE cd_eclrm (int32)
      REMOVE cd_envrn_a (int32)
      REMOVE no_route (int32)
      REMOVE cd_categ_r (int32)
      REMOVE cd_etat_ch (int32)
      REMOVE cd_aspct_r (int32)
      REMOVE cd_locln_a (int32)
      REMOVE cd_posi_ac (int32)
      REMOVE cd_confg_r (int32)
      REMOVE cd_zon_tra (int32)
      REMOVE cd_pnt_cdr (varchar(254))
      REMOVE cd_pnt_c_1 (varchar(254))
      REMOVE cd_cond_me (int32)
      REMOVE nb_veh_imp (int32)
      REMOVE nb_bless_1 (int32)
      REMOVE heure_accd (varchar(254))
      REMOVE an (int32)
      REMOVE reg_adm (varchar(254))
      REMOVE mrc (varchar(254))
      REMOVE nb_camionl (int32)
      REMOVE nb_outil_e (int32)
      REMOVE nb_tous_au (int32)
      REMOVE nb_cyclomo (int32)
      REMOVE nb_motocyc (int32)
      REMOVE nb_taxi (int32)
      REMOVE nb_urgence (int32)
      REMOVE nb_motonei (int32)
      REMOVE nb_vhr (int32)
      REMOVE nb_autres_ (int32)
      REMOVE nb_veh_non (int32)
      REMOVE nb_deces_p (int32)
      REMOVE nb_bless_2 (int32)
      REMOVE nb_victi_1 (int32)
      REMOVE nb_deces_m (int32)
      REMOVE nb_bless_3 (int32)
      REMOVE nb_victi_2 (int32)
      REMOVE nb_deces_v (int32)
      REMOVE nb_bless_4 (int32)
      REMOVE nb_victi_3 (int32)
      REMOVE vitesse_au (int32)
      REMOVE loc_x (real64)
      REMOVE loc_y (real64)
      REMOVE loc_cote_q (varchar(254))
      REMOVE loc_cote_p (int32)
      REMOVE loc_detach (varchar(254))
      REMOVE loc_imprec (varchar(254))
      REMOVE loc_long (real32)
      REMOVE loc_lat (real32)
    -> AttributeManager_24
Note: Assignation d'indices de gravité d'accident
AttributeManager_24
    ATTR_TABLE = SET_TO ind_grav_acc (int64) = FME_CONDITIONAL:DEFAULT_VALUE'0'BOOL_OP;OR;COMPOSITE_TEST;1;TEST @Value(gravite) = Mortel'-3'BOOL_OP;OR;COMPOSITE_TEST;1;TEST @Value(gravite) = Léger'-1'BOOL_OP;OR;COMPOSITE_TEST;1;TEST @Value(gravite) = Grave'-2'FME_NUM_CONDITIONS4___
    USER_EXPOSED_ATTRIBUTES = ind_grav_acc
    -> AttributeManager_25
Note: Assignation d'indice en fonction du nombre de morts/blessés
AttributeManager_25
    ATTR_TABLE:
      SET_TO ind_mort_acc (int64) = FME_CONDITIONAL:DEFAULT_VALUE'0'BOOL_OP;OR;COMPOSITE_TEST;1 OR 2;TEST @Value(nb_morts) = 2;TEST @Value(nb_morts) = 1'-1'FME_NUM_CONDITIONS2___
      SET_TO ind_bless_acc (int64) = FME_CONDITIONAL:DEFAULT_VALUE'0'BOOL_OP;OR;COMPOSITE_TEST;1;TEST @Value(nb_blesses) = 1'-1'BOOL_OP;OR;COMPOSITE_TEST;1;TEST @Value(nb_blesses) > 1'-2'FME_NUM_CONDITIONS3___
    USER_EXPOSED_ATTRIBUTES = ind_mort_acc,ind_bless_acc
    -> AttributeManager_26
Note: Assigantion d'un indice en fonction des accidents impliquant des vélos
AttributeManager_26
    ATTR_TABLE = SET_TO ind_velo_acc (int64) = FME_CONDITIONAL:DEFAULT_VALUE'0'BOOL_OP;OR;COMPOSITE_TEST;1;TEST @Value(nb_bicycle) > 1'-2'BOOL_OP;OR;COMPOSITE_TEST;1;TEST @Value(nb_bicycle) = 1'-1'FME_NUM_CONDITIONS3___
    USER_EXPOSED_ATTRIBUTES = ind_velo_acc
    -> NeighborFinder [CANDIDATE]
Note: Assigne les valeurs d'indices d'accidents aux troncons de piste cyclable le plus près
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> AttributeManager_27
    <REJECTED> -> Logger_2
Note: Ménage
AttributeManager_27
    ATTR_TABLE:
      REMOVE id (varchar(24))
      REMOVE no_seq_col (varchar(254))
      REMOVE nb_morts (int32)
      REMOVE nb_blesses (int32)
      REMOVE nb_victime (int32)
      REMOVE gravite (varchar(254))
      REMOVE nb_automob (int32)
      REMOVE nb_bicycle (int32)
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
    -> AttributeManager_21
Note: Une dizaine de points d'accidents ont une géometrie ne permettant pas à FME de les traiter dans le NeighborFinder. Comme c'est négligeable sur les 200000+ points, on va les ignorer.
Logger_2
    LOG_FEATURE = LOG_ONLY
    MAXCOORDS = 20
    MAXFEATS = 20
    MESSAGE = Feature is:
    SEVERITY = INFO

Bookmark: Entraves_travaux (contient information spatiale)
CSV (reader CSV2_1)
    attributes: id varchar(24), permit_permit_id varchar(18), boroughid varchar(41), permitcategory varchar(7), currentstatus varchar(12), duration_start_date datetime, duration_end_date datetime, reason_category varchar(138), occupancy_name varchar(69), submittercategory varchar(78), organizationname varchar(115), duration_days_mon_active varchar(1), duration_days_mon_all_day_round varchar(1), duration_days_tue_active varchar(1), duration_days_tue_all_day_round varchar(1), duration_days_wed_active varchar(1), duration_days_wed_all_day_round varchar(1), duration_days_thu_active varchar(1), duration_days_thu_all_day_round varchar(1), duration_days_fri_active varchar(1), duration_days_fri_all_day_round varchar(1), duration_days_sat_active varchar(1), duration_days_sat_all_day_round varchar(1), duration_days_sun_active varchar(1), duration_days_sun_all_day_round varchar(1), duration_days_sat_start_time varchar(5), duration_days_sat_end_time varchar(5), duration_days_mon_start_time varchar(5), duration_days_mon_end_time varchar(5), duration_days_tue_start_time varchar(5),
      duration_days_tue_end_time varchar(5), duration_days_wed_start_time varchar(5), duration_days_wed_end_time varchar(5), duration_days_thu_start_time varchar(5), duration_days_thu_end_time varchar(5), duration_days_fri_start_time varchar(5), duration_days_fri_end_time varchar(5), duration_days_sun_start_time varchar(5), duration_days_sun_end_time varchar(5), load_date datetime, longitude x_coordinate, latitude y_coordinate
    -> Reprojector_3
Reprojector_3
    DEST = EPSG:3857
    INTERPOLATION_TYPE_NAME = Nearest Neighbor
    RASTER_CELL_SIZE = Preserve Cells
    RASTER_TOLERANCE = 0.0
    REPROJECTED -> FeatureJoiner [LEFT]

Bookmark: Impacts_travaux
CSV (reader CSV2_2)
    attributes: id_request varchar(24), streetid varchar(42), streetimpactwidth varchar(12), streetimpacttype varchar(55), nbfreeparkingplace uint32, sidewalk_blockedtype varchar(52), backsidewalk_blockedtype varchar(29), bikepath_blockedtype varchar(29), name varchar(42), shortname varchar(34), fromname varchar(41), fromshortname varchar(22), toname varchar(41), toshortname varchar(22), length real32, isarterial varchar(1), stmimpact_blockedtype varchar(29), otherproviderimpact_blockedtype varchar(29), reservedlane_blockedtype varchar(29)
    -> FeatureJoiner [RIGHT]

Bookmark: Travaux
Note: On joint les informations d'impacts travaux qui n'ont pas de géométrie aux informations d'entraves travaux.
FeatureJoiner
    ATTR_CONFLICT_RES = Prefer Left
    GEOMETRY_HANDLING = Prefer Left
    JOIN_KEYS = id id_request AUTO
    JOIN_MODE = Full
    JOINED -> BulkAttributeRenamer_2
    <REJECTED> -> Logger
Note: On renomme les attributs en minuscule selon la convention
BulkAttributeRenamer_2
    ATTRCHOICE = All Attributes
    CASE_CHANGE_TYPE = lower
    MODE_CHOICE = RENAME
    PATTERN_ACTION_DISP = CASECHANGE
    -> AttributeFilter_2
    -> AttributeManager_16
Note: ON DOIT AUSSI SORTIR UNE TABLE CLEAN CLEAN AVEC LES INFORMATIONS SUR LES TRAVAUX POUR UPDATER NOTRE APPLICATION FINALE EN TEMPS REELLE AVEC LES HORAIRES DE TRAVAUX
Logger
    LOG_FEATURE = LOG_ONLY
    MAXCOORDS = 20
    MAXFEATS = 20
    MESSAGE = Feature is:
    SEVERITY = INFO

Bookmark: Obstruction - Impact circulation
Note: Filtre des obstructions
AttributeFilter_2
    ATTR_NAME = bikepath_blockedtype
    ATTR_VALUES = <Empty>,<Missing>,<Null>,<Unfiltered>,BarrÃ©e,ObstruÃ©e
    BarrÃ©e -> Junction_5
    ObstruÃ©e -> Junction_5
Junction_5
    -> AttributeManager_15
Note: Calcul d'indice d'obstruction des voies
AttributeManager_15
    ATTR_TABLE = SET_TO ind_obstr (int64) = FME_CONDITIONAL:DEFAULT_VALUE'_FME_NO_OP_'BOOL_OP;OR;COMPOSITE_TEST;1;CASE_INSENSITIVE_TEST @Value(bikepath_blockedtype) = BarrÃ©e'-9999'BOOL_OP;OR;COMPOSITE_TEST;1;TEST @Value(bikepath_blockedtype) = ObstruÃ©e'-2'FME_NUM_CONDITIONS3___
    USER_EXPOSED_ATTRIBUTES = ind_obstr
    -> Bufferer
Note: Buffer autour des obstructions car les points des travaux et les lignes des pistes cyclables ne se touchent pas
Bufferer
    ANGLE = 22.5
    CAP_STYLE = Arc
    CORNER_STYLE = Arc
    MODE = AREA
    OFFSET = 30
    OFFSET_UNITS = NONE
    PRECISION = APPROX
    BUFFERED -> SpatialFilter_4 [Filter]
    <REJECTED> -> Logger_32
Logger_32
    LOG_FEATURE = LOG_ONLY
    MAXCOORDS = 20
    MAXFEATS = 20
    MESSAGE = Feature is:
    SEVERITY = INFO
Note: Ajout des indices des données ponctuelles d'obstruction sur les données de piste cyclables avec un filtre spatial
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> Junction_6
    FAILED -> AttributeManager_17
    <REJECTED> -> Logger_31
Note: Ajout d'indice aux valeurs nulles
AttributeManager_17
    ATTR_TABLE = SET_TO ind_obstr (int64) = 0
    USER_EXPOSED_ATTRIBUTES = ind_obstr
    -> Junction_6
Note: Union des pistes cyclables et indices d'obstruction des pistes cyclables
Junction_6
    -> AttributeManager_18
Note: Ménage d'attributs superflus
AttributeManager_18
    ATTR_TABLE:
      REMOVE permitcategory (varchar(7))
      REMOVE currentstatus (varchar(12))
      REMOVE duration_start_date (datetime)
      REMOVE duration_end_date (datetime)
      REMOVE reason_category (varchar(138))
      REMOVE occupancy_name (varchar(69))
      REMOVE submittercategory (varchar(78))
      REMOVE organizationname (varchar(115))
      REMOVE duration_days_mon_active (varchar(1))
      REMOVE duration_days_mon_all_day_round (varchar(1))
      REMOVE duration_days_tue_active (varchar(1))
      REMOVE duration_days_tue_all_day_round (varchar(1))
      REMOVE duration_days_wed_active (varchar(1))
      REMOVE duration_days_wed_all_day_round (varchar(1))
      REMOVE duration_days_thu_active (varchar(1))
      REMOVE duration_days_thu_all_day_round (varchar(1))
      REMOVE duration_days_fri_active (varchar(1))
      REMOVE duration_days_fri_all_day_round (varchar(1))
      REMOVE duration_days_sat_active (varchar(1))
      REMOVE duration_days_sat_all_day_round (varchar(1))
      REMOVE duration_days_sun_active (varchar(1))
      REMOVE duration_days_sun_all_day_round (varchar(1))
      REMOVE duration_days_sat_start_time (varchar(5))
      REMOVE duration_days_sat_end_time (varchar(5))
      REMOVE duration_days_mon_start_time (varchar(5))
      REMOVE duration_days_mon_end_time (varchar(5))
      REMOVE duration_days_tue_start_time (varchar(5))
      REMOVE duration_days_tue_end_time (varchar(5))
      REMOVE duration_days_wed_start_time (varchar(5))
      REMOVE duration_days_wed_end_time (varchar(5))
      REMOVE duration_days_thu_start_time (varchar(5))
      REMOVE duration_days_thu_end_time (varchar(5))
      REMOVE duration_days_fri_start_time (varchar(5))
      REMOVE duration_days_fri_end_time (varchar(5))
      REMOVE duration_days_sun_start_time (varchar(5))
      REMOVE duration_days_sun_end_time (varchar(5))
      REMOVE load_date (datetime)
      REMOVE longitude (real64)
      REMOVE latitude (real64)
      REMOVE id_request (varchar(24))
      REMOVE streetid (varchar(42))
      REMOVE streetimpactwidth (varchar(12))
      REMOVE streetimpacttype (varchar(55))
      REMOVE nbfreeparkingplace (uint32)
      REMOVE sidewalk_blockedtype (varchar(52))
      REMOVE backsidewalk_blockedtype (varchar(29))
      REMOVE bikepath_blockedtype (varchar(29))
      REMOVE name (varchar(42))
      REMOVE shortname (varchar(34))
      REMOVE fromname (varchar(41))
      REMOVE fromshortname (varchar(22))
      REMOVE toname (varchar(41))
      REMOVE toshortname (varchar(22))
      REMOVE length (real32)
      REMOVE isarterial (varchar(1))
      REMOVE stmimpact_blockedtype (varchar(29))
      REMOVE otherproviderimpact_blockedtype (varchar(29))
      REMOVE reservedlane_blockedtype (varchar(29))
      REMOVE _predicate (buffer)
    -> SpatialFilter_5 [Candidate]
Logger_31
    LOG_FEATURE = LOG_ONLY
    MAXCOORDS = 20
    MAXFEATS = 20
    MESSAGE = Feature is:
    SEVERITY = INFO

Bookmark: Impact inconfort généré par construction
Note: Ajout d'indice pour les tronçon affectés par des travaux. Ménage des champs
AttributeManager_16
    ATTR_TABLE:
      REMOVE permitcategory (varchar(7))
      REMOVE currentstatus (varchar(12))
      REMOVE duration_start_date (datetime)
      REMOVE duration_end_date (datetime)
      REMOVE reason_category (varchar(138))
      REMOVE occupancy_name (varchar(69))
      REMOVE submittercategory (varchar(78))
      REMOVE organizationname (varchar(115))
      REMOVE duration_days_mon_active (varchar(1))
      REMOVE duration_days_mon_all_day_round (varchar(1))
      REMOVE duration_days_tue_active (varchar(1))
      REMOVE duration_days_tue_all_day_round (varchar(1))
      REMOVE duration_days_wed_active (varchar(1))
      REMOVE duration_days_wed_all_day_round (varchar(1))
      REMOVE duration_days_thu_active (varchar(1))
      REMOVE duration_days_thu_all_day_round (varchar(1))
      REMOVE duration_days_fri_active (varchar(1))
      REMOVE duration_days_fri_all_day_round (varchar(1))
      REMOVE duration_days_sat_active (varchar(1))
      REMOVE duration_days_sat_all_day_round (varchar(1))
      REMOVE duration_days_sun_active (varchar(1))
      REMOVE duration_days_sun_all_day_round (varchar(1))
      REMOVE duration_days_sat_start_time (varchar(5))
      REMOVE duration_days_sat_end_time (varchar(5))
      REMOVE duration_days_mon_start_time (varchar(5))
      REMOVE duration_days_mon_end_time (varchar(5))
      REMOVE duration_days_tue_start_time (varchar(5))
      REMOVE duration_days_tue_end_time (varchar(5))
      REMOVE duration_days_wed_start_time (varchar(5))
      REMOVE duration_days_wed_end_time (varchar(5))
      REMOVE duration_days_thu_start_time (varchar(5))
      REMOVE duration_days_thu_end_time (varchar(5))
      REMOVE duration_days_fri_start_time (varchar(5))
      REMOVE duration_days_fri_end_time (varchar(5))
      REMOVE duration_days_sun_start_time (varchar(5))
      REMOVE duration_days_sun_end_time (varchar(5))
      REMOVE load_date (datetime)
      REMOVE longitude (real64)
      REMOVE latitude (real64)
      REMOVE id_request (varchar(24))
      REMOVE streetid (varchar(42))
      REMOVE streetimpactwidth (varchar(12))
      REMOVE streetimpacttype (varchar(55))
      REMOVE nbfreeparkingplace (uint32)
      REMOVE sidewalk_blockedtype (varchar(52))
      REMOVE backsidewalk_blockedtype (varchar(29))
      REMOVE bikepath_blockedtype (varchar(29))
      REMOVE name (varchar(42))
      REMOVE shortname (varchar(34))
      REMOVE fromname (varchar(41))
      REMOVE fromshortname (varchar(22))
      REMOVE toname (varchar(41))
      REMOVE toshortname (varchar(22))
      REMOVE length (real32)
      REMOVE isarterial (varchar(1))
      REMOVE stmimpact_blockedtype (varchar(29))
      REMOVE otherproviderimpact_blockedtype (varchar(29))
      REMOVE reservedlane_blockedtype (varchar(29))
      SET_TO ind_trav (real64) = -2
    USER_EXPOSED_ATTRIBUTES = ind_trav
    -> Bufferer_5
Note: Buffer autour des obstructions car les points des travaux et les lignes des pistes cyclables ne se touchent pas
Bufferer_5
    ANGLE = 22.5
    CAP_STYLE = Arc
    CORNER_STYLE = Arc
    MODE = AREA
    OFFSET = 30
    OFFSET_UNITS = NONE
    PRECISION = APPROX
    BUFFERED -> SpatialFilter_5 [Filter]
    <REJECTED> -> Logger_33
Logger_33
    LOG_FEATURE = LOG_ONLY
    MAXCOORDS = 20
    MAXFEATS = 20
    MESSAGE = Feature is:
    SEVERITY = INFO
Note: Ajout indice sur pistes cyclables
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_7
    FAILED -> AttributeManager_19
    <REJECTED> -> Logger_34
Note: Ajout indice valeurs nulles
AttributeManager_19
    ATTR_TABLE = SET_TO ind_trav (int64) = 0
    USER_EXPOSED_ATTRIBUTES = ind_trav
    -> Junction_7
Note: Union des indices nuls et calculés pour les travaux
Junction_7
    -> AttributeManager_20
Note: Ménage d'attributs
AttributeManager_20
    ATTR_TABLE:
      REMOVE boroughid (varchar(41))
      REMOVE _overlaps (uint32)
      REMOVE objectid (int32)
      REMOVE shape_area (real64)
      REMOVE shape_leng (real64)
      REMOVE legende (varchar(254))
      REMOVE longueur_2 (real64)
      REMOVE pente_pourc (real64)
      REMOVE _predicate (buffer)
    -> NeighborFinder [BASE]
Logger_34
    LOG_FEATURE = LOG_ONLY
    MAXCOORDS = 20
    MAXFEATS = 20
    MESSAGE = Feature is:
    SEVERITY = INFO

Bookmark: Production de raster de pentes
GEOTIFF (reader GEOTIFF_1) [off]
    attributes: datatype char(255)
mnt_mtl_50 (reader POSTGIS_RASTER_2)
    attributes: datatype varchar(255)
    -> Reprojector_8
Reprojector_8
    DEST = EPSG:3857
    INTERPOLATION_TYPE_NAME = Nearest Neighbor
    RASTER_CELL_SIZE = Preserve Cells
    RASTER_TOLERANCE = 0.0
    REPROJECTED -> PORV_debut [RASTER]
    REPROJECTED -> PORV_fin [RASTER]
Note: Extraction de valeurs d'élévation associés au points de début et fin de segments de pistes cyclables afin de calculer la pente de chaque segment éventuellement
PORV_debut: PointOnRasterValueExtractor
    INTERPOLATION_TYPE_NAME = Nearest Neighbor
    POINT -> AttributeCreator
Note: On rajoute les valeurs d'élévation du raster au nouveau champ elevation
AttributeCreator
    ATTR_TABLE = SET_TO elevation_debut (varchar(200)) = @Evaluate(@Value(_band{0}.value))
    -> FeatureJoiner_2 [LEFT]
PORV_fin: PointOnRasterValueExtractor
    INTERPOLATION_TYPE_NAME = Nearest Neighbor
    POINT -> AttributeCreator_2
AttributeCreator_2
    ATTR_TABLE = SET_TO elevation_fin (varchar(200)) = @Evaluate(@Value(_band{0}.value))
    -> FeatureJoiner_2 [RIGHT]
FeatureJoiner_2
    ATTR_CONFLICT_RES = Prefer Left
    GEOMETRY_HANDLING = Prefer Left
    JOIN_KEYS = segmentnumber segmentnumber AUTO
    JOIN_MODE = Full
    JOINED -> AttributeManager_3
    <REJECTED> -> Logger_8
Note: Calcul de la difference d'élévation de chaque segment à partir de la longueur, et les élévations d'extrémités. Ménage
AttributeManager_3
    ATTR_TABLE:
      REMOVE fme_basename (varchar(52))
      REMOVE id_cycl (number(18,0))
      REMOVE protege_4s (varchar(80))
      REMOVE rev_avan_1 (varchar(80))
      REMOVE route_vert (varchar(80))
      REMOVE saisons4 (varchar(80))
      REMOVE separateur (varchar(80))
      REMOVE separate_1 (varchar(80))
      REMOVE type_voie_ (varchar(80))
      REMOVE type_voi_1 (varchar(80))
      REMOVE n_coord (int64)
      REMOVE x_debut (real64)
      REMOVE y_debut (real64)
      REMOVE x_fin (real64)
      REMOVE y_fin (real64)
      REMOVE _band{}.value (real64)
      SET_TO diff_elev (real32) = @Evaluate(@sqrt((@Value(elevation_fin)-@Value(elevation_debut))**2))
    USER_EXPOSED_ATTRIBUTES = diff_elev
    -> FeatureJoiner_3 [LEFT]
Note: On obtient le fichier de lignes de troncons de pistes cyclables avec des valeurs de pentes moyennes du troncon
FeatureJoiner_3
    ATTR_CONFLICT_RES = Prefer Left
    GEOMETRY_HANDLING = Prefer Right
    JOIN_KEYS = segmentnumber segmentnumber AUTO
    JOIN_MODE = Full
    JOINED -> AttributeManager_22
    <REJECTED> -> Logger_9
Note: Calcul de la pente et menage
AttributeManager_22
    ATTR_TABLE:
      REMOVE _band{}.palette{}.value (real64)
      REMOVE elevation_debut (varchar(200))
      REMOVE elevation_fin (varchar(200))
      REMOVE id_cycl (number(18,0))
      REMOVE protege_4s (varchar(80))
      REMOVE rev_avan_1 (varchar(80))
      REMOVE route_vert (varchar(80))
      REMOVE saisons4 (varchar(80))
      REMOVE separateur (varchar(80))
      REMOVE separate_1 (varchar(80))
      REMOVE type_voie_ (varchar(80))
      REMOVE type_voi_1 (varchar(80))
      REMOVE n_coord (int64)
      SET_TO pente_pourc (real32) = @Evaluate((@Value(diff_elev)/@Value(longueur_2))*100)
    USER_EXPOSED_ATTRIBUTES = pente_pourc
    -> AttributeManager_23
Note: Attribution de l'indice de pente en fonction des catégories prédéfinies
Note: Ajout de l'indice de chaleur aux segments de piste cyclable correspondants
AttributeManager_23
    ATTR_TABLE:
      REMOVE diff_elev (real32)
      SET_TO ind_pente (real64) = FME_CONDITIONAL:DEFAULT_VALUE'0'BOOL_OP;AND;COMPOSITE_TEST;1 AND 2;TEST @Value(pente_pourc) >= 2;TEST @Value(pente_pourc) < 5'-1'BOOL_OP;AND;COMPOSITE_TEST;1 AND 2;TEST @Value(pente_pourc) >= 5;TEST @Value(pente_pourc) < 8'-2'BOOL_OP;AND;COMPOSITE_TEST;1;TEST @Value(pente_pourc) >= 8'-3'FME_NUM_CONDITIONS4___
    USER_EXPOSED_ATTRIBUTES = ind_pente
    -> SpatialFilter [Candidate]
Logger_9
    LOG_FEATURE = LOG_ONLY
    MAXCOORDS = 20
    MAXFEATS = 20
    MESSAGE = Feature is:
    SEVERITY = INFO
Logger_8
    LOG_FEATURE = LOG_ONLY
    MAXCOORDS = 20
    MAXFEATS = 20
    MESSAGE = Feature is:
    SEVERITY = INFO

Bookmark: îlots_de_chaleur
ilots-de-chaleur-images-satellite-2023 (reader SHAPEFILE_2)
    attributes: Temp_Class double, Shape_Area double, Shape_Leng double, Legende varchar(254)
    -> Reprojector_2
Reprojector_2
    DEST = EPSG:3857
    INTERPOLATION_TYPE_NAME = Nearest Neighbor
    RASTER_CELL_SIZE = Preserve Cells
    RASTER_TOLERANCE = 0.0
    REPROJECTED -> BulkAttributeRenamer_3
Note: On renomme les attributs en minuscule selon la convention
BulkAttributeRenamer_3
    ATTRCHOICE = All Attributes
    CASE_CHANGE_TYPE = lower
    MODE_CHOICE = RENAME
    PATTERN_ACTION_DISP = CASECHANGE
    -> AttributeManager_4
Note: Création d'un indice d'îlot de chaleur et assignation de valeurs en fonction du niveau de chaleur
AttributeManager_4
    ATTR_TABLE:
      REMOVE temp_class (real64)
      SET_TO ind_chaleur (int64) = FME_CONDITIONAL:DEFAULT_VALUE'0'BOOL_OP;OR;COMPOSITE_TEST;1;TEST @Value(legende) = Îlot de fraîcheur'2'BOOL_OP;OR;COMPOSITE_TEST;1;TEST @Value(legende) = Température plus froide que la moyenne'1'BOOL_OP;OR;COMPOSITE_TEST;1;TEST @Value(legende) = Température plus chaude que la moyenne (à risque)'-1'BOOL_OP;OR;COMPOSITE_TEST;1;TEST @Value(legende) = Îlot de chaleur'-2'FME_NUM_CONDITIONS5___
    USER_EXPOSED_ATTRIBUTES = ind_chaleur
    -> GeometryExtractor_3
GeometryExtractor_3
    ATTR = _geometry
    KIND_LONG = FME Binary
    REMOVE_GEOMETRY = No
    -> SpatialFilter [Filter]
    <REJECTED> -> Logger_11
Note: On obtient pistes cyclables + indices cyclables + indice chaleur
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = DISJOINT
    USE_BOUNDING_BOX = No
    PASSED -> SpatialFilter_2 [Candidate]
    <REJECTED> -> Logger_12
Logger_12
    LOG_FEATURE = LOG_ONLY
    MAXCOORDS = 20
    MAXFEATS = 20
    MESSAGE = Feature is:
    SEVERITY = INFO
Logger_11
    LOG_FEATURE = LOG_ONLY
    MAXCOORDS = 20
    MAXFEATS = 20
    MESSAGE = Feature is:
    SEVERITY = INFO

Bookmark: Indice_final_total
Note: Addition des indices spécifiques en indice total pour chaque troncon de piste cyclable
AttributeManager_21
    ATTR_TABLE = SET_TO ind_total (int64) = @Evaluate(@add(@Value(ind_bless_acc),@Value(ind_chaleur),@Value(ind_grav_acc),@Value(ind_mort_acc),@Value(ind_pente),@Value(ind_sep_voie),@Value(ind_trav),@Value(ind_typ_voie),@Value(ind_velo_acc),@Value(ind_vert),@Value(ind_voie_princ)))
    USER_EXPOSED_ATTRIBUTES = geodb_raster_compression_quality,ind_total
    -> FeatureJoiner_4 [LEFT]
Note: Ajout des tronçons de route et jointure attributaire
FeatureJoiner_4
    ATTR_CONFLICT_RES = Prefer Left
    GEOMETRY_HANDLING = Prefer Left
    JOIN_KEYS = id_trc id_trc AUTO
    JOIN_MODE = Inner
    JOINED -> Junction_8
    UNJOINED_LEFT -> LineOnAreaOverlayer [LINE]
    <REJECTED> -> FeatureJoiner_4__Rejected_
FeatureJoiner_4__Rejected_: Logger
    LOG_FEATURE = LOG_ONLY
    MAXCOORDS = 20
    MAXFEATS = 20
    MESSAGE = Feature is:
    SEVERITY = INFO
Note: Jointure spatiale sur les parcs pour ceux qui n'ont pas de route
LineOnAreaOverlayer
    ATTR_ACCUM_MODE = Merge Incoming
    ATTR_CONFLICT_RES = Use Original
    CLEANING_TOLERANCE = Automatic
    DEAGGREGATE_INPUT = Yes
    OVERLAY_TYPE = LINE_ON_AREA
    OV_ATTR = _overlaps
    LINE -> AttributeFilter_4
    <REJECTED> -> LineOnAreaOverlayer__Rejected_
Note: Au moins une jointure
AttributeFilter_4
    ATTR_NAME = _overlaps
    ATTR_VALUES = <Empty>,<Missing>,<Null>,<Unfiltered>,0
    <UNFILTERED> -> Tester
Junction_8
    -> AttributeManager_28
Note: Ménage des attributs
AttributeManager_28
    ATTR_TABLE:
      REMOVE deb_gch (int32)
      REMOVE fin_gch (int32)
      REMOVE arr_gch (varchar(200))
      REMOVE sens_cir (int32)
      REMOVE classe (int32)
      REMOVE lie_voie (varchar(10))
      REMOVE typ_voie (varchar(15))
      REMOVE dir_voie (varchar(5))
      REMOVE deb_drt (int32)
      REMOVE fin_drt (int32)
      REMOVE arr_drt (varchar(200))
      REMOVE lim_gch (varchar(30))
      REMOVE lim_drt (varchar(30))
      REMOVE position (int32)
      REMOVE OBJECTID (int32)
      REMOVE Type (varchar(200))
      REMOVE Lien (varchar(200))
      REMOVE Nom (varchar(200))
      REMOVE NUM_INDEX (varchar(200))
      REMOVE SUPERFICIE (varchar(200))
      REMOVE PROPRIETE (varchar(200))
      REMOVE GESTION (varchar(200))
      REMOVE COMPETENCE (varchar(200))
      REMOVE TYPO1 (varchar(200))
      REMOVE TYPO2 (varchar(200))
      REMOVE _overlaps (uint32)
    -> Aggregator
    -> StatisticsCalculator
    -> Tester_4
Note: Tronçons de travaux majeurs
Tester_4
    BOOL_OP = OR
    TEST_CLAUSE = TEST @Value(ind_obstr) < -2
    TEST_MODE = TEST
    PASSED -> AttributeKeeper
AttributeKeeper
    CREATE_BULK_MODE_FEATURES = NO
    KEEP_ATTRS = id_trc
    -> ChangeDetector [REVISED]
FeatureJoiner_5__Rejected_: Logger
    LOG_FEATURE = LOG_ONLY
    MAXCOORDS = 20
    MAXFEATS = 20
    MESSAGE = Feature is:
    SEVERITY = INFO
LineOnAreaOverlayer__Rejected_: Logger
    LOG_FEATURE = LOG_ONLY
    MAXCOORDS = 20
    MAXFEATS = 20
    MESSAGE = Feature is:
    SEVERITY = INFO

Bookmark: Normaliser les noms de parc
Tester
    BOOL_OP = AND
    TEST_CLAUSE:
      TEST Type ATTRIBUTE_HAS_A_VALUE ""
      TEST Lien ATTRIBUTE_HAS_A_VALUE ""
    TEST_MODE = TEST
    PASSED -> StringConcatenator
    FAILED -> Tester_2
StringConcatenator
    ACTION = Create New Attribute
    PARM_LINE = fme_basicstring:12%1%12%1%11:@Value(Type) @Value(Lien) @Value(Nom)
    VAL_ATTR = nom_voie
    -> Junction_9
Tester_2
    BOOL_OP = AND
    TEST_CLAUSE:
      TEST Lien NOT_ATTRIBUTE_HAS_A_VALUE ""
      TEST Type NOT_ATTRIBUTE_HAS_A_VALUE ""
    TEST_MODE = TEST
    PASSED -> StringConcatenator_2
    FAILED -> Tester_3
StringConcatenator_2
    ACTION = Create New Attribute
    PARM_LINE = fme_basicstring:11:@Value(Nom)
    VAL_ATTR = nom_voie
    -> Junction_9
Tester_3
    BOOL_OP = OR
    TEST_CLAUSE = TEST Type ATTRIBUTE_HAS_A_VALUE ""
    TEST_MODE = TEST
    PASSED -> StringConcatenator_3
    FAILED -> StringConcatenator_4
StringConcatenator_3
    ACTION = Create New Attribute
    PARM_LINE = fme_basicstring:12%1%11:@Value(Type) @Value(Nom)
    VAL_ATTR = nom_voie
    -> Junction_9
StringConcatenator_4
    ACTION = Create New Attribute
    PARM_LINE = fme_basicstring:12%1%11:@Value(Lien) @Value(Nom)
    VAL_ATTR = nom_voie
    -> Junction_9
Junction_9
    -> AttributeFilter_5
AttributeFilter_5
    ATTR_NAME = nom_voie
    ATTR_VALUES = <Empty>,<Missing>,<Null>,<Unfiltered>
    <UNFILTERED> -> Junction_8

Bookmark: Nombre de tronçon par rue / parc
Aggregator
    ACCUM_ATTRS_NAME = Drop Incoming Attributes
    AGGREGATE_TYPE = Homogeneous Collection (If Possible)
    GROUP_BY = nom_voie
    MODE = Geometry - Assemble One Level
    SEP = ,
    AGGREGATE -> FeatureJoiner_5 [LEFT]
StatisticsCalculator
    CALCULATION_MODE = NUMERIC
    FEAT_STATS = ind_total,NUMERIC_MODE,,,,SUM,,,,,,,,,
    GROUP_BY = nom_voie
    SUMMARY -> FeatureJoiner_5 [RIGHT]
FeatureJoiner_5
    ATTR_CONFLICT_RES = Prefer Left
    GEOMETRY_HANDLING = Prefer Left
    JOIN_KEYS = nom_voie nom_voie AUTO
    JOIN_MODE = Full
    JOINED -> LengthCalculator
    <REJECTED> -> FeatureJoiner_5__Rejected_

Bookmark: Calcul du ratio et filtrage
LengthCalculator
    DIM = 2
    LEN_ATTR = longueur
    MULT = 1
    -> AttributeManager_29
AttributeManager_29
    ATTR_TABLE:
      SET_TO longueur (real64) = FME_CONDITIONAL:DEFAULT_VALUE'FME_NULL_VALUE'BOOL_OP;OR;COMPOSITE_TEST;1;TEST @Value(longueur) >= 100'@Value(longueur)'FME_NUM_CONDITIONS2___
      SET_TO ratio (real64) = @Evaluate(@Value(ind_total.sum)/@Value(longueur))
    -> AttributeFilter_3
AttributeFilter_3
    ATTR_NAME = longueur
    ATTR_VALUES = <Empty>,<Missing>,<Null>,<Unfiltered>
    <UNFILTERED> -> pistes_cyclables_agreables (writer POSTGIS_1)

Bookmark: Importation PostgreSQL
Note: Écriture des pistes cyclables agréables dans PostgreSQL
pistes_cyclables_agreables (writer POSTGIS_1)
    attributes: nom_voie varchar(100), ind_total_sum float8, longueur float8, ratio float8
zone_travaux (reader POSTGIS_4)
    attributes: date_debut timestamp, date_fin timestamp, id_trc int4
    -> Tester_6
Note: Voir si les travaux sont déjà terminés
Tester_6
    BOOL_OP = OR
    TEST_CLAUSE = TEST date_fin ATTRIBUTE_VALUE_NULL ""
    TEST_MODE = TEST
    PASSED -> ChangeDetector [ORIGINAL]
    FAILED -> FeatureJoiner_6 [LEFT]
Note: Vérification des changements entre les données BD existantes et celles entrantes
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCHATTRS = id_trc
    MATCH_STRATEGY = Match Selected Attributes
    PREEMPTIVE_ATTRS = id_trc
    UNCHANGED_OUTPUT = Output Original
    UPSERT_MODE = No
    INSERTED -> FeatureJoiner_6 [RIGHT]
    DELETED -> AttributeCreator_4
Note: S'assurer qu'une nouvelle entrée ne correspond pas à un tronçon fermé
FeatureJoiner_6
    ATTR_CONFLICT_RES = Prefer Left
    GEOMETRY_HANDLING = Prefer Left
    JOIN_KEYS = id_trc id_trc AUTO
    JOIN_MODE = Inner
    UNJOINED_RIGHT -> AttributeCreator_3
    <REJECTED> -> FeatureJoiner_6__Rejected_
AttributeCreator_3
    ATTR_TABLE:
      SET_TO date_debut (datetime) = @DateTimeNow()
      SET_TO date_fin (datetime) = FME_NULL_VALUE
    -> FeatureWriter [Output]
Note: Écriture en BD
FeatureWriter
    DATASET = FH791176
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = FH791176
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
FeatureJoiner_6__Rejected_: Logger
    LOG_FEATURE = LOG_ONLY
    MAXCOORDS = 20
    MAXFEATS = 20
    MESSAGE = Feature is:
    SEVERITY = INFO
AttributeCreator_4
    ATTR_TABLE:
      SET_TO date_debut (datetime) = @Value(date_debut)
      SET_TO date_fin (datetime) = @DateTimeNow()
    -> AttributeManager_30
Note: Fermer l'entrée de travaux en ajoutant une date de fin
AttributeManager_30
    ATTR_TABLE = SET_TO fme_db_operation (char(9)) = UPDATE
    -> FeatureWriter_3 [Output]
Note: Écriture en BD
FeatureWriter_3
    DATASET = FH791176
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = FH791176
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
